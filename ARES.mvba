Attribute VB_Name = "Config"
' Module: Config
' Description: This module provides functions to manage configuration variables in MicroStation with silent error handling.
' It includes functions to get, set, and delete configuration variables, ensuring that operations are performed
' without interrupting the workflow in case of errors. The module is designed to maintain the integrity of
' configuration variables by checking their existence before performing operations and handling errors.

Option Explicit

' Function to get the value of a configuration variable
Public Function GetVar(ByVal Key As String) As String
    On Error GoTo ErrorHandler

    ' Initialize the return value
    GetVar = ""

    ' Check if the configuration variable is defined
    If Application.ActiveWorkspace.IsConfigurationVariableDefined(Key) Then
        ' Retrieve the value of the configuration variable
        GetVar = Application.ActiveWorkspace.ConfigurationVariableValue(Key)
    End If

    Exit Function

ErrorHandler:
    GetVar = ""
End Function

' Function to set the value of a configuration variable
Public Function SetVar(ByVal Key As String, ByVal Value As String) As Boolean
    On Error GoTo ErrorHandler

    ' Initialize the return value
    SetVar = False

    ' Check if the configuration variable is defined
    If Application.ActiveWorkspace.IsConfigurationVariableDefined(Key) Then
        ' Replace the existing variable
        SetVar = ReplaceVar(Key, Value)
    Else
        ' Create a new variable
        SetVar = CreateVar(Key, Value)
    End If

    Exit Function

ErrorHandler:
    SetVar = False
End Function

' Function to delete a configuration variable
Public Function DeleteVar(ByVal Key As String) As Boolean
    On Error GoTo ErrorHandler

    ' Initialize the return value
    DeleteVar = False

    ' Check if the configuration variable is defined
    If Application.ActiveWorkspace.IsConfigurationVariableDefined(Key) Then
        ' Remove the configuration variable
        Application.ActiveWorkspace.RemoveConfigurationVariable Key
        DeleteVar = True
    End If

    Exit Function

ErrorHandler:
    DeleteVar = False
End Function

' Private function to create a new configuration variable
Private Function CreateVar(ByVal Key As String, ByVal Value As String) As Boolean
    On Error GoTo ErrorHandler

    ' Initialize the return value
    CreateVar = False

    ' Check if the variable does not exist and the value is not empty
    If Not Application.ActiveWorkspace.IsConfigurationVariableDefined(Key) And Value <> "" Then
        ' Add the new configuration variable
        Application.ActiveWorkspace.AddConfigurationVariable Key, Value
        CreateVar = True
    End If

    Exit Function

ErrorHandler:
    CreateVar = False
End Function

' Private function to replace the value of an existing configuration variable
Private Function ReplaceVar(ByVal Key As String, ByVal Value As String) As Boolean
    On Error GoTo ErrorHandler

    ' Initialize the return value
    ReplaceVar = False

    ' Delete the existing variable and create a new one with the same key
    If DeleteVar(Key) Then
        ReplaceVar = CreateVar(Key, Value)
    End If

    Exit Function

ErrorHandler:
    ReplaceVar = False
End Function

Attribute VB_Name = "Length"
' Module: Length
' Description: This module provides functions to calculate lengths of elements in MicroStation with silent error handling.
' The module includes functions to determine the length of various element types, handle rounding logic,
' and manage configuration variables for rounding.
' NEVER USE Rnd = 255 in GetLength function ! it reserved for error

Const ARES_RND_VAR As String = "ARES_RND"
Const ARES_RND_DEFAULT As Byte = 1
Const ARES_RND_ERROR_VALUE As Byte = 255

Option Explicit

' Public function to get the length of an element
Public Function GetLength(ByVal El As Element, Optional Rnd As Variant, Optional RndLength As Boolean = True, Optional ErasRnd As Boolean = False) As Double
    On Error GoTo ErrorHandler

    ' Determine the length based on the element type
    GetLength = GetElementLength(El)

    ' Handle rounding if required
    If RndLength Then
        Rnd = HandleRounding(Rnd, ErasRnd)
        If Rnd = ARES_RND_ERROR_VALUE Then
            ShowStatus "Valeur d'arrondi interdit: " & ARES_RND_ERROR_VALUE
            GetLength = 0
            Exit Function
        End If
        GetLength = RoundedLength(GetLength, CByte(Rnd))
    ElseIf ErasRnd Then
        If Not HandleRoundingForErase(Rnd) Then
            GetLength = 0
            Exit Function
        End If
    End If

    Exit Function

ErrorHandler:
    GetLength = 0
End Function

' Private function to get the length of an element based on its type
Private Function GetElementLength(ByVal El As Element) As Double
    On Error GoTo ErrorHandler
    
    ' Determine the length based on the element type
    Select Case True
        Case El.IsComplexStringElement
            GetElementLength = El.AsComplexStringElement.Length
        Case El.IsComplexShapeElement
            GetElementLength = LengthComplexShape(El)
        Case El.IsLineElement
            GetElementLength = El.AsLineElement.Length
        Case El.IsArcElement
            GetElementLength = El.AsArcElement.Length
        Case Else
            GetElementLength = 0
    End Select

    Exit Function

ErrorHandler:
    GetElementLength = 0
End Function

' Private function to handle rounding logic
Private Function HandleRounding(Optional Rnd As Variant, Optional ErasRnd As Boolean) As Variant
    On Error GoTo ErrorHandler
    
    ' Handle missing rounding value
    If IsMissing(Rnd) Then
        Rnd = GetRoundValue()
    ElseIf ErasRnd And (VarType(Rnd) = vbByte Or VarType(Rnd) = vbInteger) Then
        ' Set rounding value if erase rounding is true
        If Not SetRound(CByte(Rnd)) Then
            HandleRounding = ARES_RND_ERROR_VALUE
            Exit Function
        End If
    End If
    HandleRounding = Rnd
    
    Exit Function

ErrorHandler:
    HandleRounding = ARES_RND_ERROR_VALUE
End Function

' Private function to handle rounding logic for erase
Private Function HandleRoundingForErase(Optional Rnd As Variant) As Boolean
    On Error GoTo ErrorHandler
    
    HandleRoundingForErase = False
    
    ' Set default rounding if Rnd is missing
    If IsMissing(Rnd) Then
        If Not SetRound(ARES_RND_DEFAULT) Then Exit Function
        ShowStatus ARES_RND_VAR & " défini à " & ARES_RND_DEFAULT & " par défaut"
    ElseIf VarType(Rnd) = vbByte Or VarType(Rnd) = vbInteger Then
        ' Set rounding value if Rnd is provided
        If Not SetRound(CByte(Rnd)) Then Exit Function
    End If
    
    HandleRoundingForErase = True
    Exit Function

ErrorHandler:
    HandleRoundingForErase = False
End Function

' Private function to get the rounding value
Private Function GetRoundValue() As Variant
    On Error GoTo ErrorHandler

    Dim roundValue As String
    roundValue = GetRound()
    
    ' Handle empty rounding value
    If roundValue = "" Then
        If Not SetRound(ARES_RND_DEFAULT) Then Exit Function
        roundValue = GetRound()
        If roundValue = "" Then Exit Function
        ShowStatus ARES_RND_VAR & " défini à " & ARES_RND_DEFAULT & " par défaut"
    End If
    GetRoundValue = CByte(roundValue)

    Exit Function

ErrorHandler:
    GetRoundValue = ARES_RND_ERROR_VALUE
End Function

' Private function to get the rounding configuration variable
Private Function GetRound() As String
    On Error GoTo ErrorHandler
    
    GetRound = Config.GetVar(ARES_RND_VAR)
    Exit Function
    
ErrorHandler:
    GetRound = ""
End Function

' Private function to set the rounding configuration variable
Private Function SetRound(Rnd As Byte) As Boolean
    On Error GoTo ErrorHandler
    
    SetRound = Config.SetVar(ARES_RND_VAR, Rnd)
    Exit Function
    
ErrorHandler:
    SetRound = False
End Function

' Private function to calculate the length of a complex shape element
Private Function LengthComplexShape(ByVal El As ComplexShapeElement) As Double
    On Error GoTo ErrorHandler

    Dim ELEnum As ElementEnumerator
    Dim SubEl As Element
    Dim i As Long

    LengthComplexShape = El.Perimeter
    Set ELEnum = El.GetSubElements

    ' Iterate through sub-elements
    For i = 0 To UBound(ELEnum.BuildArrayFromContents)
        ELEnum.MoveNext
    Next

    Set SubEl = ELEnum.Current
    If SubEl.IsLineElement Then
        LengthComplexShape = (LengthComplexShape - (SubEl.AsLineElement.Length * 2)) / 2
    Else
        LengthComplexShape = 0
    End If

    Exit Function

ErrorHandler:
    LengthComplexShape = 0
End Function

' Private function to round the length to a specified number of decimal places
Private Function RoundedLength(Length As Double, Rnd As Byte) As Double
    On Error GoTo ErrorHandler
    
    RoundedLength = Round(Length, Rnd)
    Exit Function
    
ErrorHandler:
    RoundedLength = 0
End Function

Attribute VB_Name = "test"
Sub Test_ARES()
    Dim Result As Boolean
    Dim Result2 As String
    
    Result = Config.SetVar("Test_ARES", "Test_LECLERE")
    
    ShowStatus Result
    
    Result2 = Config.GetVar("Test_ARES")
    
    ShowStatus Result2
End Sub
Sub Test_ARES2()
    Dim Result As Boolean
    Dim Result2 As String
    
    Config.SetVar "Test_ARES", "Test_LECLERE_remplace"
    Result2 = Config.GetVar("Test_ARES")
    
    ShowStatus Result2
    
    Result = Config.DeleteVar("Test_ARES")
    
    ShowStatus Result
End Sub

Sub testlenght()
    Dim El As Element
    Dim Lenght As Double
    Dim Id As DLong
    
    Id = DLongFromLong(122)
    Set El = ActiveModelReference.GetElementByID(Id)
    
    Lenght = Length.GetLength(El)
    Lenght = Length.GetLength(El, 8, True, True)
    Lenght = Length.GetLength(El, , False, True)
End Sub
